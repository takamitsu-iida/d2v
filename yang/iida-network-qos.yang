module iida-network-qos {
  yang-version 1.1;
  namespace "urn:iida:params:xml:ns:yang:iida-network-qos";
  prefix "nqos";

  import iida-network-model {
    prefix "nnm";
  }

  organization "IIDA Inc.";
  contact "takamitsu iida";
  description
    "QoS (Quality of Service) extension for iida-network-model.
     Adds named policy-set definitions (class-maps with match/action)
     under network-model and binds them to Layer 3 interfaces.";

  revision "2026-08-06" {
    description "Initial version.";
  }

  // ===========================================================================
  // QoS policy definitions — placed under /network-model
  // ===========================================================================
  augment "/nnm:network-model" {
    container qos {
      description "QoS policy sets defined for the network.";

      list policy-set {
        key "name";
        description "A named QoS policy (analogous to a policy-map).";
        leaf name {
          type string { length "1..64"; }
          description "Unique policy set name.";
        }
        leaf description {
          type string;
          description "Human-readable description.";
        }

        list class-map {
          key "name";
          description "Traffic class within this policy (analogous to a class-map).";
          leaf name {
            type string { length "1..64"; }
            description "Class-map name (e.g., VOICE, VIDEO, BEST-EFFORT).";
          }
          container match {
            description "Traffic classification criteria.";
            leaf dscp {
              type uint8 { range "0..63"; }
              description "Match on DSCP value.";
            }
            leaf protocol {
              type enumeration {
                enum "ip";
                enum "tcp";
                enum "udp";
                enum "icmp";
              }
              description "Match on IP protocol.";
            }
            leaf acl-name {
              type string { length "1..64"; }
              description "Name of an ACL (iida-network-acl) to use as a match criterion.";
            }
          }
          container action {
            description "QoS treatment applied to matched traffic.";
            leaf bandwidth-kbps {
              type uint32;
              units "kbps";
              description "Guaranteed minimum bandwidth for this class.";
            }
            leaf max-bandwidth-kbps {
              type uint32;
              units "kbps";
              description "Maximum bandwidth ceiling (shaping/policing).";
            }
            leaf burst-size-bytes {
              type uint32;
              units "bytes";
              description "Token-bucket burst allowance for policing or shaping.";
            }
            leaf set-dscp {
              type uint8 { range "0..63"; }
              description "Re-mark DSCP on matched traffic.";
            }
            leaf queue-priority {
              type enumeration {
                enum "strict";   // LLQ / strict-priority — served before all other queues
                enum "normal";
              }
              default "normal";
              description "Queue scheduling priority for this class.";
            }
          }
        }
      }
    }
  }

  // ===========================================================================
  // Interface QoS binding — applied to layer3-interface-config
  // ===========================================================================
  augment "/nnm:network-model/nnm:layer3-layer/nnm:layer3-interface-config" {
    container qos-binding {
      description "QoS policies applied to this Layer 3 interface.";
      leaf ingress-policy {
        type leafref {
          path "/nnm:network-model/nqos:qos/nqos:policy-set/nqos:name";
        }
        description "Policy applied to inbound traffic (classification and marking).";
      }
      leaf egress-policy {
        type leafref {
          path "/nnm:network-model/nqos:qos/nqos:policy-set/nqos:name";
        }
        description "Policy applied to outbound traffic (queuing and shaping).";
      }
    }
  }
}
