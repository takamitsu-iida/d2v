module iida-network-model {
  yang-version 1.1;
  namespace "urn:iida:params:xml:ns:yang:iida-network-model";
  prefix "nnm";

  include iida-network-model-physical;
  include iida-network-model-l2;
  include iida-network-model-l3;
  include iida-network-model-mgmt;

  organization "IIDA Inc.";
  contact "takamitsu iida";
  description
    "A concise YANG model for representing network topology across physical, Layer 2, and Layer 3.
     Composed from submodules: physical, l2, l3, mgmt.
     Extended by independent modules: iida-network-acl, iida-network-qos, iida-network-nat.";

  revision "2026-08-06" {
    description "Refactor: split monolithic module into submodules (physical, l2, l3, mgmt).
                 Schema tree is unchanged; only file structure was reorganized.";
  }
  revision "2026-07-17" {
    description "IPv6 support: generalize inet:ipv4-address/ipv4-prefix to
                 inet:ip-address/ip-prefix, widen prefix-length to 0..128,
                 and rename ipv4-routing container to protocol-agnostic routing.
                 Also fix port-type enum labels (copper/fiber).
                 Redundancy: add layer2-layer/link-aggregation (LAG/LACP, MLAG)
                 and layer3-layer/first-hop-redundancy (VRRP/HSRP/GLBP).
                 Dynamic routing: add layer3-layer/routing-config (BGP, OSPF,
                 redistribution) and reusable layer3-layer/route-policy.
                 Management: add network-model/management (mgmt VLAN, per-device
                 mgmt IP/gateway, in-band mgmt IF, mgmt loopback, out-of-band).
                 Add optional physical-connection endpoint lag-ref to explicitly
                 mark a connection as a link-aggregation member.";
  }
  revision "2026-07-01" {
    description "Add asn/loopback to device, ip-address to interface,
                 ethernet enum to port-type, and replace flat connection
                 endpoints with endpoint list for IP CLOS topology support.";
  }
  revision "2023-11-20" {
    description "Initial version, inspired by OpenConfig-like structure.";
  }

  // ===========================================================================
  // Top-level container — content delegated to submodules via groupings
  // ===========================================================================
  container network-model {
    description "Top-level container for the entire network configuration.";
    uses physical-layer-group;
    uses layer2-layer-group;
    uses layer3-layer-group;
    uses management-group;
  }
}
