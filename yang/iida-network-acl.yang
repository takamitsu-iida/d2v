module iida-network-acl {
  yang-version 1.1;
  namespace "urn:iida:params:xml:ns:yang:iida-network-acl";
  prefix "nacl";

  import iida-network-model {
    prefix "nnm";
  }
  import ietf-inet-types {
    prefix "inet";
  }

  organization "IIDA Inc.";
  contact "takamitsu iida";
  description
    "ACL (Access Control List) extension for iida-network-model.
     Adds named ACL definitions under network-model and binds them
     to Layer 3 interfaces in ingress/egress direction.";

  revision "2026-08-06" {
    description "Initial version.";
  }

  // ===========================================================================
  // ACL set definitions — placed under /network-model
  // ===========================================================================
  augment "/nnm:network-model" {
    container acl {
      description "Named ACL sets used across the network.";

      list acl-set {
        key "name";
        description "A named access control list.";
        leaf name {
          type string { length "1..64"; }
          description "Unique ACL name (e.g., PERMIT-WEB, DENY-SSH-INBOUND).";
        }
        leaf type {
          type enumeration {
            enum "ipv4";
            enum "ipv6";
            enum "mixed";
          }
          default "ipv4";
          description "Address family this ACL applies to.";
        }
        leaf description {
          type string;
          description "Human-readable description.";
        }
        list acl-entry {
          key "sequence";
          description "Ordered ACE clauses; evaluated lowest sequence first.";
          leaf sequence {
            type uint32;
            description "Evaluation order (lower = higher priority).";
          }
          leaf description {
            type string;
            description "Entry description.";
          }
          container match {
            description "Traffic match criteria for this entry.";
            leaf protocol {
              type enumeration {
                enum "any";
                enum "ip";
                enum "tcp";
                enum "udp";
                enum "icmp";
                enum "icmpv6";
              }
              default "any";
              description "IP protocol to match.";
            }
            leaf source-address {
              type inet:ip-prefix;
              description "Source IP prefix (e.g., 10.0.0.0/8). Omit to match any.";
            }
            leaf destination-address {
              type inet:ip-prefix;
              description "Destination IP prefix. Omit to match any.";
            }
            leaf source-port {
              type uint16;
              description "TCP/UDP source port (exact match). Omit to match any.";
            }
            leaf destination-port {
              type uint16;
              description "TCP/UDP destination port (exact match). Omit to match any.";
            }
          }
          leaf action {
            type enumeration {
              enum "permit";
              enum "deny";
              enum "permit-log";  // permit and log
              enum "deny-log";    // deny and log
            }
            mandatory true;
            description "Action taken when this entry matches.";
          }
        }
      }
    }
  }

  // ===========================================================================
  // Interface ACL binding — applied to layer3-interface-config
  // ===========================================================================
  augment "/nnm:network-model/nnm:layer3-layer/nnm:layer3-interface-config" {
    container acl-binding {
      description "ACL applied to this Layer 3 interface.";
      leaf ingress {
        type leafref {
          path "/nnm:network-model/nacl:acl/nacl:acl-set/nacl:name";
        }
        description "ACL evaluated on inbound (received) traffic.";
      }
      leaf egress {
        type leafref {
          path "/nnm:network-model/nacl:acl/nacl:acl-set/nacl:name";
        }
        description "ACL evaluated on outbound (transmitted) traffic.";
      }
    }
  }
}
