submodule iida-network-model-l3 {
  yang-version 1.1;
  belongs-to iida-network-model {
    prefix "nnm";
  }

  import ietf-inet-types {
    prefix "inet";
  }

  description
    "Layer 3 definitions: IP subnets, interface addressing, static routes,
     first-hop redundancy, route policies, and dynamic routing (BGP/OSPF).";

  // ===========================================================================
  // Layer 3
  // ===========================================================================
  grouping layer3-layer-group {
    container layer3-layer {
      description "Details about IP addressing and routing configurations.";

      list ip-subnet {
        key "subnet-id";
        description "Definition of IP subnets used in the network.";
        leaf subnet-id {
          type string;
          description "Unique identifier for the subnet.";
        }
        leaf prefix {
          type inet:ip-prefix;
          description "IP network prefix in CIDR format.";
        }
        leaf description {
          type string;
          description "Description of the subnet.";
        }
        leaf associated-vlan-id {
          type leafref {
            path "../../../layer2-layer/vlan/vlan-id";
          }
          mandatory false;
          description "Optional: Reference to the VLAN associated with this subnet.";
        }
      }

      list layer3-interface-config {
        key "device-id interface-id";
        description "Layer 3 configuration (IP addressing) for a specific interface on a device.";
        leaf device-id {
          type leafref {
            path "../../../physical-layer/device/device-id";
          }
          description "Reference to the physical device.";
        }
        leaf interface-id {
          type leafref {
            path "../../../physical-layer/device[device-id=current()/../device-id]/interface/interface-id";
          }
          description "Reference to the physical interface on that device.";
        }
        list addresses {
          key "ip-address";
          description "IP addresses configured on this interface.";
          leaf ip-address {
            type inet:ip-address;
            description "IP address configured on the interface.";
          }
          leaf prefix-length {
            type uint8 {
              range "0..128";
            }
            description "Prefix length for the IP address (0..32 for IPv4, 0..128 for IPv6).";
          }
          leaf associated-subnet-id {
            type leafref {
              path "../../../ip-subnet/subnet-id";
            }
            mandatory false;
            description "Optional: Reference to the IP subnet this address belongs to.";
          }
        }
        leaf ip-routing-enabled {
          type boolean;
          default "true";
          description "If IP routing is enabled on this interface.";
        }
        container routing {
          description "Layer 3 routing settings for the interface (IPv4/IPv6).";
          leaf ospf-area {
            type string;
            description "OSPF area ID configured on this interface (e.g., '0.0.0.0', '1').";
          }
        }
      }

      list host-config {
        key "device-id";
        description "Layer 3 configuration (IP addressing) for host devices.";
        leaf device-id {
          type leafref {
            path "../../../physical-layer/device/device-id";
          }
          description "Reference to the physical host device.";
        }
        leaf primary-ip-address {
          type inet:ip-address;
          description "Primary IP address of the host.";
        }
        leaf primary-prefix-length {
          type uint8 {
            range "0..128";
          }
          description "Prefix length for the primary IP address (0..32 for IPv4, 0..128 for IPv6).";
        }
        leaf default-gateway {
          type inet:ip-address;
          description "Default gateway IP address for the host.";
        }
        leaf associated-subnet-id {
          type leafref {
            path "../../ip-subnet/subnet-id";
          }
          mandatory false;
          description "Optional: Reference to the IP subnet this host belongs to.";
        }
      }

      list static-route {
        key "destination-prefix next-hop";
        description "Global static routes configured on routing devices.";
        leaf device-id {
          type leafref {
            path "../../../physical-layer/device/device-id";
          }
          description "Device on which this static route is configured.";
        }
        leaf destination-prefix {
          type inet:ip-prefix;
          description "Destination network prefix in CIDR format.";
        }
        leaf next-hop {
          type inet:ip-address;
          description "Next-hop IP address.";
        }
        leaf administrative-distance {
          type uint8;
          default "1";
          description "Administrative distance of the route.";
        }
      }

      list first-hop-redundancy {
        key "device-id interface-id group-id";
        description
          "First-hop gateway redundancy (VRRP/HSRP/GLBP) providing a shared
           virtual IP across multiple routers for host default gateways.";
        leaf device-id {
          type leafref {
            path "../../../physical-layer/device/device-id";
          }
          description "Device participating in this redundancy group.";
        }
        leaf interface-id {
          type leafref {
            path "../../../physical-layer/device[device-id=current()/../device-id]/interface/interface-id";
          }
          description "Interface on which the redundancy group runs.";
        }
        leaf group-id {
          type uint16 {
            range "0..4095";
          }
          description "Redundancy group / VRID / HSRP group number.";
        }
        leaf protocol {
          type enumeration {
            enum "vrrp";
            enum "hsrp";
            enum "glbp";
          }
          description "First-hop redundancy protocol in use.";
        }
        leaf virtual-ip-address {
          type inet:ip-address;
          description "Shared virtual IP address acting as the default gateway.";
        }
        leaf priority {
          type uint8;
          default "100";
          description "Election priority; higher becomes master/active.";
        }
        leaf preempt {
          type boolean;
          default "true";
          description "Whether a higher-priority node preempts the current master.";
        }
      }

      list route-policy {
        key "name";
        description
          "Reusable routing policies (route-maps) referenced by BGP peers and
           redistribution to filter or manipulate route attributes.";
        leaf name {
          type string {
            length "1..128";
          }
          description "Unique policy name.";
        }
        leaf description {
          type string;
          description "Human-readable description of the policy.";
        }
        list statement {
          key "sequence";
          description "Ordered policy clauses evaluated by ascending sequence.";
          leaf sequence {
            type uint32;
            description "Evaluation order of this clause.";
          }
          leaf action {
            type enumeration {
              enum "permit";
              enum "deny";
            }
            description "Whether matching routes are accepted or rejected.";
          }
          leaf match-prefix {
            type inet:ip-prefix;
            description "Match routes falling within this prefix (simplified single match).";
          }
          leaf set-local-preference {
            type uint32;
            description "BGP LOCAL_PREF to set on matched routes.";
          }
          leaf set-metric {
            type uint32;
            description "Metric/MED to set on matched routes.";
          }
        }
      }

      list routing-config {
        key "device-id";
        description
          "Per-device dynamic routing configuration (BGP/OSPF) and route
           redistribution. Per-interface OSPF area assignment lives in
           layer3-interface-config/routing/ospf-area.";
        leaf device-id {
          type leafref {
            path "../../../physical-layer/device/device-id";
          }
          description "Device on which these routing protocols run.";
        }
        leaf router-id {
          type inet:ip-address;
          description "Global router ID used by OSPF/BGP.";
        }

        container bgp {
          presence "BGP is enabled on this device.";
          description "BGP configuration for this device.";
          leaf local-asn {
            type uint32;
            mandatory true;
            description "Local BGP Autonomous System Number.";
          }
          list peer-group {
            key "name";
            description "Reusable BGP peer templates shared by neighbors.";
            leaf name {
              type string {
                length "1..64";
              }
              description "Peer group name.";
            }
            leaf peer-asn {
              type uint32;
              description "Remote ASN for members (omit for internal/iBGP).";
            }
            leaf import-policy {
              type leafref {
                path "../../../../route-policy/name";
              }
              description "Inbound route policy applied to received routes.";
            }
            leaf export-policy {
              type leafref {
                path "../../../../route-policy/name";
              }
              description "Outbound route policy applied to advertised routes.";
            }
          }
          list neighbor {
            key "neighbor-address";
            description "BGP neighbors (sessions).";
            leaf neighbor-address {
              type inet:ip-address;
              description "Neighbor peer IP address.";
            }
            leaf peer-asn {
              type uint32;
              description "Remote ASN of the neighbor.";
            }
            leaf peer-group {
              type leafref {
                path "../../peer-group/name";
              }
              description "Peer group this neighbor inherits configuration from.";
            }
            leaf description {
              type string;
              description "Neighbor description.";
            }
            leaf-list address-family {
              type enumeration {
                enum "ipv4-unicast";
                enum "ipv6-unicast";
                enum "l2vpn-evpn";
              }
              description "Address families negotiated with this neighbor.";
            }
            leaf import-policy {
              type leafref {
                path "../../../../route-policy/name";
              }
              description "Inbound route policy (overrides peer-group).";
            }
            leaf export-policy {
              type leafref {
                path "../../../../route-policy/name";
              }
              description "Outbound route policy (overrides peer-group).";
            }
          }
        }

        container ospf {
          presence "OSPF is enabled on this device.";
          description "OSPFv2/v3 configuration for this device.";
          leaf process-id {
            type string;
            description "OSPF process identifier.";
          }
          list area {
            key "area-id";
            description "OSPF areas configured on this device.";
            leaf area-id {
              type string;
              description "Area identifier (e.g., '0.0.0.0', '1').";
            }
            leaf area-type {
              type enumeration {
                enum "standard";
                enum "stub";
                enum "nssa";
              }
              default "standard";
              description "Area type.";
            }
          }
        }

        list redistribution {
          key "source-protocol destination-protocol";
          description "Redistribution of routes from one protocol into another.";
          leaf source-protocol {
            type enumeration {
              enum "connected";
              enum "static";
              enum "ospf";
              enum "bgp";
              enum "rip";
            }
            description "Protocol whose routes are redistributed.";
          }
          leaf destination-protocol {
            type enumeration {
              enum "ospf";
              enum "bgp";
            }
            description "Protocol into which routes are injected.";
          }
          leaf route-policy {
            type leafref {
              path "../../../route-policy/name";
            }
            description "Optional policy to filter/modify redistributed routes.";
          }
          leaf metric {
            type uint32;
            description "Metric assigned to redistributed routes.";
          }
        }
      }
    } // end layer3-layer
  } // end layer3-layer-group
}
