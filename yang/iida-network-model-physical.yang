submodule iida-network-model-physical {
  yang-version 1.1;
  belongs-to iida-network-model {
    prefix "nnm";
  }

  import ietf-inet-types {
    prefix "inet";
  }
  import ietf-yang-types {
    prefix "yang";
  }

  description
    "Physical layer definitions: devices, interfaces, and physical connections.";

  // ===========================================================================
  // Common Groupings (used by physical-layer and cross-referenced by other layers)
  // ===========================================================================
  grouping device-identification {
    leaf device-id {
      type string {
        pattern '[a-zA-Z0-9_-]+';
        length "1..64";
      }
      description "Unique identifier for a network device.";
    }
    leaf device-name {
      type string {
        length "1..128";
      }
      description "Human-readable name of the device.";
    }
    leaf device-type {
      type enumeration {
        enum "router";
        enum "switch";
        enum "server";
        enum "firewall";
        enum "host";
        enum "load-balancer";
      }
      description "Functional type of the device.";
    }
  }

  grouping interface-identification {
    leaf interface-id {
      type string {
        pattern '[a-zA-Z0-9_./-]+';
        length "1..128";
      }
      description "Unique identifier for an interface within a device (e.g., Gi0/1, eth0).
                   This should be the canonical name that is used in configuration.";
    }
  }

  // ===========================================================================
  // Physical Layer
  // ===========================================================================
  grouping physical-layer-group {
    container physical-layer {
      description "Details about physical devices and their interconnections.";

      list device {
        key "device-id";
        description "List of all physical network devices.";
        uses device-identification;
        leaf vendor {
          type string;
          description "Vendor of the device (e.g., Cisco, Juniper).";
        }
        leaf model {
          type string;
          description "Model name of the device.";
        }
        leaf os-version {
          type string;
          description "Operating System version of the device.";
        }
        leaf serial-number {
          type string {
            length "1..64";
          }
          description "Hardware serial number of the device for asset management.";
        }
        leaf role {
          type enumeration {
            enum "spine";
            enum "leaf";
            enum "core";
            enum "distribution";
            enum "access";
            enum "border";
            enum "oob";        // out-of-band management device
            enum "other";
          }
          description "Operational role of the device within the network fabric.";
        }
        container location {
          description "Structured physical location of the device.";
          leaf site-id {
            type string { length "1..64"; }
            description "Site or campus identifier.";
          }
          leaf building {
            type string { length "1..64"; }
            description "Building name or code within the site.";
          }
          leaf room {
            type string { length "1..64"; }
            description "Room or floor designation within the building.";
          }
          leaf rack-id {
            type string { length "1..64"; }
            description "Rack identifier (e.g., 'Rack-A01').";
          }
          leaf rack-unit {
            type uint8 { range "1..52"; }
            units "U";
            description "Rack unit (U) position of the device (top of device).";
          }
        }
        leaf hw-revision {
          type string { length "1..32"; }
          description "Hardware revision identifier for distinguishing variants of the same model.";
        }
        leaf install-date {
          type yang:date-and-time;
          description "Date when the device was installed.";
        }
        leaf end-of-life-date {
          type yang:date-and-time;
          description "Vendor end-of-life date for lifecycle management.";
        }
        leaf asn {
          type uint32;
          description "BGP Autonomous System Number assigned to this device.";
        }
        leaf loopback {
          type inet:ip-prefix;
          description "Primary loopback IP address in CIDR notation (e.g., 10.0.0.1/32, 2001:db8::1/128).";
        }
        leaf zone {
          type string {
            length "1..64";
          }
          description
            "Diagram zone for grouping devices into Graphviz subgraph clusters.
             Examples: 'core', 'dmz', 'branch-a', 'wan-edge'";
        }

        list interface {
          key "interface-id";
          description "Physical interfaces of the device.";
          uses interface-identification;
          leaf description {
            type string;
            description "Description of the interface.";
          }
          leaf port-type {
            type enumeration {
              enum "ethernet";          // Generic Ethernet (media type unspecified)
              enum "ethernet-copper";   // Copper Ethernet
              enum "ethernet-fiber";    // Fiber Ethernet
              enum "serial";
              enum "other";
            }
            description "Indicates the physical port's media type.";
          }
          leaf hardware-mac-address {
            type yang:mac-address;
            description "MAC address of the physical interface.";
          }
          leaf port-speed-gbps {
            type uint16;
            units "Gbps";
            description "Nominal speed of the port in Gbps.";
          }
          leaf ip-address {
            type inet:ip-prefix;
            description "IP address with prefix length assigned to this interface
                         in CIDR notation (e.g., 10.1.0.0/31, 10.0.0.1/32, 2001:db8::1/64).";
          }
        }
      }

      list physical-connection {
        key "connection-id";
        description "Direct physical cable connections between interfaces.";
        leaf connection-id {
          type string;
          description "Unique identifier for the physical connection.";
        }
        list endpoint {
          key "device-id";
          min-elements 2;
          max-elements 2;
          description "The two endpoint devices and interfaces of this physical connection.";
          leaf device-id {
            type leafref {
              path "../../../device/device-id";
            }
            description "Identifier of the endpoint device.";
          }
          leaf interface-id {
            type leafref {
              path "../../../device[device-id=current()/../device-id]/interface/interface-id";
            }
            description "Identifier of the interface on the endpoint device.";
          }
          leaf lag-ref {
            type leafref {
              path "../../../../layer2-layer/link-aggregation[device-id=current()/../device-id]/lag-id";
            }
            description
              "Optional explicit reference to the link-aggregation group (on this
               endpoint's device) that this connection is a member of. When set,
               it authoritatively marks the connection as a LAG member link,
               removing the need to infer membership from interface-id matching.
               Optional: if omitted, LAG membership is inferred from the device's
               link-aggregation/member-interface list.";
          }
        }
        leaf cable-type {
          type string; // e.g., "Cat6", "SMF" (Single-Mode Fiber)
          description "Type of cable used (e.g., Cat6, OS2 fiber).";
        }
        leaf length-meters {
          type decimal64 {
            fraction-digits 2;
            range "0.01 .. max";
          }
          units "meters";
          description "Approximate length of the cable in meters.";
        }
      }
    } // end physical-layer
  } // end physical-layer-group
}
