module iida-network-nat {
  yang-version 1.1;
  namespace "urn:iida:params:xml:ns:yang:iida-network-nat";
  prefix "nnat";

  import iida-network-model {
    prefix "nnm";
  }
  import ietf-inet-types {
    prefix "inet";
  }

  organization "IIDA Inc.";
  contact "takamitsu iida";
  description
    "NAT (Network Address Translation) extension for iida-network-model.
     Adds per-device NAT configuration (address pools, static mappings,
     dynamic PAT rules) under network-model and marks Layer 3 interfaces
     as NAT inside or outside.";

  revision "2026-08-06" {
    description "Initial version.";
  }

  // ===========================================================================
  // NAT per-device configuration — placed under /network-model
  // ===========================================================================
  augment "/nnm:network-model" {
    container nat {
      description "NAT configuration per device in the network.";

      list nat-instance {
        key "device-id";
        description "NAT configuration on a specific device (router/firewall).";
        leaf device-id {
          type leafref {
            path "/nnm:network-model/nnm:physical-layer/nnm:device/nnm:device-id";
          }
          description "Device on which NAT is configured.";
        }

        list pool {
          key "name";
          description "Named public address pool for dynamic NAT/PAT.";
          leaf name {
            type string { length "1..64"; }
            description "Pool name (e.g., OUTSIDE-POOL-1).";
          }
          leaf start-address {
            type inet:ip-address;
            mandatory true;
            description "First usable public IP address in the pool.";
          }
          leaf end-address {
            type inet:ip-address;
            mandatory true;
            description "Last usable public IP address in the pool.";
          }
        }

        list static-entry {
          key "inside-address";
          description "Static one-to-one NAT mapping (private ↔ public).";
          leaf inside-address {
            type inet:ip-address;
            description "Private (inside local) IP address.";
          }
          leaf outside-address {
            type inet:ip-address;
            mandatory true;
            description "Public (outside global) translated IP address.";
          }
        }

        list dynamic-rule {
          key "id";
          description "Dynamic NAT or PAT rule mapping inside traffic to a pool.";
          leaf id {
            type uint32;
            description "Rule identifier; rules are evaluated in ascending order.";
          }
          leaf description {
            type string;
            description "Human-readable description of the rule.";
          }
          leaf pool-name {
            type leafref {
              path "../../pool/name";
            }
            description "Address pool used as the translation source.";
          }
          leaf overload {
            type boolean;
            default "false";
            description "Enable PAT (overload) — many private addresses share one public address using port multiplexing.";
          }
        }
      }
    }
  }

  // ===========================================================================
  // Interface NAT direction — applied to layer3-interface-config
  // ===========================================================================
  augment "/nnm:network-model/nnm:layer3-layer/nnm:layer3-interface-config" {
    container nat-direction {
      description "NAT role of this Layer 3 interface.";
      leaf inside {
        type boolean;
        default "false";
        description "Set to true if this interface faces the private (inside) network.";
      }
      leaf outside {
        type boolean;
        default "false";
        description "Set to true if this interface faces the public (outside) network.";
      }
    }
  }
}
